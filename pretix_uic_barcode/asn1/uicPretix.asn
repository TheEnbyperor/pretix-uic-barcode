ASN-Module-Pretix DEFINITIONS AUTOMATIC TAGS ::= BEGIN

    PretixTicket ::= SEQUENCE {
		uniqueId VisibleString (SIZE (1..255)),

		orderYear INTEGER (2016..2269),
		orderDay INTEGER (1..366),
		orderTime INTEGER (0..1440),

   		eventSlug VisibleString (SIZE (1..50) ^ FROM ("a".."z"|"A".."Z"|"0".."9"|"."|"-")),
		itemId INTEGER,
		subeventId INTEGER OPTIONAL,
		variationId INTEGER OPTIONAL,

		attendeeName UTF8String OPTIONAL,

		validFromYear INTEGER (2016..2269) OPTIONAL,
		validFromDay INTEGER (1..366) OPTIONAL,
		validFromTime INTEGER (0..1439) OPTIONAL,

		validUntilYear INTEGER (2016..2269) OPTIONAL,
		validUntilDay INTEGER (1..366) OPTIONAL,
		validUntilTime INTEGER (0..1439) OPTIONAL,

		hasTotp BOOLEAN,

		...
	}
	
	PretixOrder ::= SEQUENCE {
		organiserSlug VisibleString (SIZE (1..50) ^ FROM ("a".."z"|"A".."Z"|"0".."9"|"."|"-")),
		eventSlug VisibleString (SIZE (1..50) ^ FROM ("a".."z"|"A".."Z"|"0".."9"|"."|"-")),
		orderCode VisibleString (SIZE (1..16) ^ FROM ("ABCDEFGHJKLMNPQRSTUVWXYZ379")),
		orderPosition INTEGER,
		orderPositionSecret VisibleString (SIZE (1..32) ^ FROM ("a".."z"|"0".."9")) OPTIONAL,
		orderSecret VisibleString (SIZE (1..32) ^ FROM ("a".."z"|"0".."9")) OPTIONAL
	}

	VASPretixTicket ::= SEQUENCE {
		uniqueId VisibleString (SIZE (1..255)),

		eventSlug VisibleString (SIZE (1..50) ^ FROM ("a".."z"|"A".."Z"|"0".."9"|"."|"-")),
		itemId INTEGER,
		subeventId INTEGER OPTIONAL,
		variationId INTEGER OPTIONAL,

		validFromYear INTEGER (2016..2269) OPTIONAL,
		validFromDay INTEGER (1..366) OPTIONAL,
		validFromTime INTEGER (0..1439) OPTIONAL,

		validUntilYear INTEGER (2016..2269) OPTIONAL,
		validUntilDay INTEGER (1..366) OPTIONAL,
		validUntilTime INTEGER (0..1439) OPTIONAL
	}

END
