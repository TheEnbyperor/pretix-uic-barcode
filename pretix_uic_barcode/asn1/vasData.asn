ASN-Module-Header DEFINITIONS AUTOMATIC TAGS ::= BEGIN

	VASData ::= SEQUENCE {
		data SEQUENCE SIZE (0..15) OF DataType
	}

	DataType ::= SEQUENCE {
		dataFormat	IA5String (SIZE (1..4) ^ FROM ("A".."Z"|"0".."9")),
		data		OCTET STRING (SIZE (1..64))
	}

END
